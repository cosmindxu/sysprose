package Big {
    part def T1;
    part def T2;
    part def T3;
    part def T4;
    part def T5;
    part def T6;
    part def T7;
    part def T8;
    part def T9;
    part def T10;
    part def T11;
    part def T12;
    part def T13;
    part def T14;
    part def T15;
    part def T16;
    part def T17;
    part def T18;
    part def T19;
    part def T20;
    part def T21;
    part def T22;
    part def T23;
    part def T24;
    part def T25;
    part def T26;
    part def T27;
    part def T28;
    part def T29;
    part def T30;
    part def T31;
    part def T32;
    part def T33;
    part def T34;
    part def T35;
    part def T36;
    part def T37;
    part def T38;
    part def T39;
    part def T40;
}
